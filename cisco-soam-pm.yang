module cisco-soam-pm {
  namespace "urn:cisco:params:xml:ns:yang:cisco-soam-pm";
  prefix cisco-soam-pm;

  import cisco-cfm {
    prefix cfm;
    revision-date 2015-09-29;
  }

  import ietf-yang-types {
    prefix yang;
  }

  organization
    "Cisco Systems, Inc.
     Customer Service

     Postal: 170 W Tasman Drive
     San Jose, CA 95134

     Tel: +1 1800 553-NETS
     
     E-mail: cs-yang@cisco.com";

  contact
    "Richard Furness - rfurness@cisco.com";

  description 
    "This YANG module contains the management data definitions for
     the management of Ethernet Services Operations, Administration
     and Maintenance for Performance Monitoring and extends the
     Connectivity Fault Management (CFM) YANG modules.

     This module is derived from the mef-soam-pm module defined in
     MEF 39. However there are a number of differences from the
     mef-soam-fm model, which fall into the following categories:
     - Bug fixes
     - Change to improve extensibility and maintainability (e.g.
       use of identities not enums, structural changes)
     
     Reference Overview:
      A number of base documents have been used to create the
      SOAM PM YANG Module.
      The following are the abbreviations for the baseline documents:
      [802.1q] refers to IEEE 802.1Q-2011 'IEEE Standard for Local
          and metropolitan area networks --Media Access Control (MAC)
          Bridges and Virtual Bridged Local Area Networks, August
          2011
      [MEF SOAM PM IA] refers to 'Service OAM Performance Monitoring
          Implementation Agreement', January 2012
      [MEF SOAM PM MIB] refers to 'Service OAM Performance Monitoring
          Definition of Managed Objects', January 2012
      [Y.1731] refers to ITU-T Y.1731 'OAM functions and mechanisms
          for Ethernet based networks', July 2011";

  revision "2015-09-29" {
    description
      "Initial revision";
  }

  //
  // Features
  //
  feature availability {
    description
      "The device supports measuring 'availability'.";
  }
  feature frame-delay-range {
    description
      "The device supports measuring 'frame delay range'.";
  }

  //
  // Type definitions related to MEF SOAM PM
  //

  typedef suspect-status-type {
    type boolean;
    description 
      "This boolean data type indicates whether the measurement
       interval has been marked as suspect.
             
       The object is set to false at the start of a measurement
       interval. It is set to true when there is a discontinuity in
       the performance measurements during the measurement interval.
       Conditions for a discontinuity include, but are not limited to
       the following:
             
         1 - The local time-of-day clock is adjusted by at least 10
             seconds
         2 - The conducting of a performance measurement is halted
             before the current measurement interval is completed
         3 - A local test, failure, or reconfiguration that disrupts
             service";
    reference
      "[MEF SOAM PM IA] R39, R40, 41 and R42";
  }

  typedef performance-monitoring-interval-type {
    type uint32 {
      range "3..3600000";
    }
    units ms;
    description
      "This integer data type indicates the transmission time between
       the SOAM PM frames for session, in ms.";
  }
  typedef test-pattern-type {
    type enumeration {
      enum null-signal-without-crc-32 {
        description
          "This test pattern is a Null signal without CRC-32.";
      }
      enum null-signal-with-crc-32 {
        description
          "This test pattern is a Null signal with CRC-32.";
      }
      enum prbs-2311-without-crc-32 {
        description
          "This test pattern is a PRBS 2^31-1 without CRC-32.";
      }
      enum prbs-2311-with-crc-32 {
        description
          "This test pattern is a PRBS 2^31-1 with CRC-32.";
      }
    }

    description
      "This enumeration data type indicates the type of test pattern
       to be sent in an OAM PDU Data TLV.";
    reference
      "MEF-SOAM-TC-MIB.MefSoamTcTestPatternType";
  }

  typedef session-status-type {
    type enumeration {
      enum active {
        description
          "Indicates the measurement instance is active.";
      }
      enum not-active {
        description
          "Indicates the measurement instance is not active.";
      }
    }

    description
      "This enumeration data type defines the status of PM session of
       a MEP.";
    reference
      "MEF-SOAM-TC-MIB.MefSoamTcStatusType";
  }

  typedef availability-type {
    type enumeration {
      enum available {
        description
          "Indicates the MEP is available.";
      }
      enum unavailable {
        description
          "Indicates the MEP is unavailable.";
      }
      enum unknown {
        description
          "Indicates the availability is not known, for instance
           because insufficient time has passed to make an
           availability calculation, the time has been excluded
           because of a maintenance interval, or because availability
           measurement is not enabled.";
      }
    }

    description
      "This enumeration data type defines the availability of a
       session, measured by a loss measurement session.";
    reference
      "MEF-SOAM-TC-MIB.MefSoamTcAvailabilityType";
  }

  identity metric-type {
    description
      "Base identity for the set of metrics that may be measured.";
  }
  identity forward-flr {
    base metric-type;
    description
      "Metric type for one-way Frame Loss Ratio in the forward
       direction.

       The flr value is a ratio that is expressed as a percent with a
       value of 0 (ratio 0.00) through 100000 (ratio 1.00).
                 
       Units are in milli-percent, where 1 indicates 0.001 percent.";
  }
  identity backward-flr {
    base metric-type;
    description
      "Metric type for one-way Frame Loss Ratio in the backward
       direction.

       The flr value is a ratio that is expressed as a percent with a
       value of 0 (ratio 0.00) through 100000 (ratio 1.00).
                 
       Units are in milli-percent, where 1 indicates 0.001 percent.";
  }
  identity forward-availability-flr {
    //@@@ yang 1.1
    //if-feature availability;
    base metric-type;
    description
      "Metric type for one-way availability FLR in the forward
       direction.
       There is one availability flr value for each 'delta_t' time
       period within the Measurement Interval, as specified in MEF
       10.2.1.
                 
       The flr value is a ratio that is expressed as a percent with a
       value of 0 (ratio 0.00) through 100000 (ratio 1.00).
                 
       Units are in milli-percent, where 1 indicates 0.001 percent.";
  }
  identity backward-availability-flr {
    //@@@ yang 1.1
    //if-feature availability;
    base metric-type;
    description
      "Metric type for one-way availability FLR in the backward
       direction.
       There is one availability flr value for each 'delta_t' time
       period within the Measurement Interval, as specified in MEF
       10.2.1.
                 
       The flr value is a ratio that is expressed as a percent with a
       value of 0 (ratio 0.00) through 100000 (ratio 1.00).
                 
       Units are in milli-percent, where 1 indicates 0.001 percent.";
  }
  identity two-way-frame-delay {
    base metric-type;
    description
      "Metric type for two-way Frame Delay.

       This metric is not supported if measurement-type is
       dm1-transmitted or dm1-received.

       Units are microseconds.";
  }
  identity forward-frame-delay {
    base metric-type;
    description
      "Metric type for one-way Frame Delay in the forward direction.

       The value of this metric may not be accurate in the absence of
       sufficiently precise clock synchronization.

       This metric is not supported if measurement-type is
       dm1-transmitted.

       Units are microseconds.";
  }
  identity backward-frame-delay {
    base metric-type;
    description
      "Metric type for one-way Frame Delay in the backward direction.

       The value of this metric may not be accurate in the absence of
       sufficiently precise clock synchronization.

       This metric is not supported if measurement-type is
       dm1-transmitted or dm1-received.

       Units are microseconds.";
  }
  identity two-way-inter-frame-delay-variation {
    base metric-type;
    description
      "Metric type for two-way Inter-frame Delay Variation.

       This metric is not supported if measurement-type is
       dm1-transmitted or dm1-received.

       Units are microseconds.";
  }
  identity forward-inter-frame-delay-variation {
    base metric-type;
    description
      "Metric type for one-way Inter-frame Delay Variation in the
       forward direction.

       This metric is not supported if measurement-type is
       dm1-transmitted.

       Units are microseconds.";
  }
  identity backward-inter-frame-delay-variation {
    base metric-type;
    description
      "Metric type for one-way Inter-frame Delay Variation in the
       backward direction.

       This metric is not supported if measurement-type is
       dm1-transmitted or dm1-received.

       Units are microseconds.";
  }
  identity two-way-frame-delay-range {
    //@@@ yang 1.1
    //if-feature frame-delay-range;
    base metric-type;
    description
      "Metric type for two-way Frame Delay Range.

       This metric is not supported if measurement-type is
       dm1-transmitted or dm1-received.

       Units are microseconds.";
  }
  identity forward-frame-delay-range {
    //@@@ yang 1.1
    //if-feature frame-delay-range;
    base metric-type;
    description
      "Metric type for one-way Frame Delay Range in the forward
       direction.

       This metric is not supported if measurement-type is
       dm1-transmitted.

       Units are microseconds.";
  }
  identity backward-frame-delay-range {
    //@@@ yang 1.1
    //if-feature frame-delay-range;
    base metric-type;
    description
      "Metric type for one-way Frame Delay Range in the backward
       direction.

       This metric is not supported if measurement-type is
       dm1-transmitted or dm1-received.

       Units are microseconds.";
  }

  identity loss-counter-type {
    description
      "Base identity for the set of loss counter types. These are
       metric types for which a simple count is the only result for
       a given Measurement Interval.";
  }
  identity transmitted-frames {
    base loss-counter-type;
    description
      "The number of frames transmitted in the specified direction,
       for loss measurement calculations.

       For a PM Session of type lmm or ccm this includes Ethernet
       Service Frames and SOAM PDUs that are in a higher MEG level
       only.
                 
       For a PM Session of type slm this includes the count of SOAM
       ETH-SLM frames only.";
  }
  identity received-frames {
    base loss-counter-type;
    description
      "The number of frames received in the specified direction by
       this MEP.
                 
       For a PM Session of types lmm or ccm this includes Ethernet
       Service Frames and SOAM PDUs that are in a higher MEG level
       only.
                 
       For a PM Session of type slm this includes the count of SOAM
       ETH-SLM frames only.";
  }
  identity high-loss {
    base loss-counter-type;
    description
      "The number of high loss intervals (HLI) in the specified
       direction during the Measurement Interval.
                 
       The value starts at 0 and increments for every HLI that
       occurs. This parameter is equivalent to 'L Sub T' found in MEF
       10.2.1..";
  }
  identity consecutive-high-loss {
    base loss-counter-type;
    description
      "The number of consecutive high loss intervals (CHLI) in the
       specified direction during the Measurement Interval.
                 
       The value starts at 0 and increments for every HLI that
       occurs. This parameter is equivalent to 'B Sub T' found in
       MEF 10.2.1..";
  }
  identity available {
    //@@@ yang 1.1
    //if-feature availability;
    base loss-counter-type;
    description
      "The number of availability indicators during a small time
       interval evaluated as available (low frame loss) in the
       specified direction by this MEP during this Measurement
       Interval.";
  }
  identity unavailable {
    //@@@ yang 1.1
    //if-feature availability;
    base loss-counter-type;
    description
      "The number of availability indicators during a small time
       interval evaluated as unavailable (high frame loss) in the
       specified direction by this MEP during this Measurement
       Interval.";
  }

  typedef remote-mep {
    type union {
      type cfm:mep-id-type;
      type yang:mac-address;
    }
    description
      "A value to identify the remote MEP with which a PM session is
       associated, either by:
       MEP ID:
         The Maintenance Association End Point Identifier of
         another MEP in the same Maintenance Association. This is
         not valid for dual-ended operations of 'rx' type, for which
         the source MAC address must be specified instead.

       or

       MAC address:
         For single-ended operations this is used to specify the
         unicast destination MAC address. For dual-ended operations
         of 'tx' type this is a unicast destination MAC address or a
         multicast address indicating the level of the MEG. For
         dual-ended operations of type 'rx' this is the source MAC
         address from which SOAM packets will be received.
       .";
  }

  //
  // Groupings related to MEF SOAM PM
  //

  grouping on-demand-timing-group {
    description
      "This grouping includes objects used for scheduling of
       on-demand PM measurement sessions.";

    container start-time {
      description
        "This container defines the on-demand session start time";

      choice start-time {
        mandatory true;
        description
          "Measurement session start time can be immediate, relative
           or absolute.";

        container immediate {
          presence "Start the measurement session immediately.";

          description
            "This object specifies the start time to be immediately
             at the time of session creation.";
        }
        leaf relative {
          type yang:timeticks;

          description 
            "This object specifies the relative start time, from the
             current system time, to start the session.";
        }
        leaf absolute {
          type yang:date-and-time;

          description 
            "This object specifies the scheduled date/time to start
             the session.";
        }
      }
    }

    container stop-time {
      description
        "This container defines the on-demand session stop time";

      choice stop-time {
        mandatory true;
        description
          "Measurement session stop time can be none, relative or
           absolute.";

        container none {
          presence "Never end the measurement session.";

          description
            "This object specifies the measurement session to never
             end.";
        }

        leaf relative {
          type yang:timeticks;
          mandatory true;

          description 
            "This object specifies the duration of the session. The
             duration time can be specified as forever (represented
             by a zero value) or as relative time (e.g. a given
             number of hours, minutes, and seconds from the start
             time).  If the duration time is relative time, then the
             duration time should be equal to or greater than the
             frame transmission period of the PM function(s)
             comprising the PM Solution";
              
        }

        leaf absolute {
          type yang:date-and-time;

          description 
            "This object specifies the scheduled date and time to
             stop the PM session. The stop date and time value should
             be greater than or equal to the scheduled start date and
             time.";
        }
      }
    }
  }

  identity pm-packet-type {
    description
      "Base identity for the set of Performance Monitoring packet
       types.";
  }

  identity lm-packet-type {
    base pm-packet-type;
    description
      "Base identity for the set of Loss Measurement 'types'.";
  }
  identity lmm {
    base lm-packet-type;
    description
      "LMM SOAM PDU generated and received LMR responses tracked.";
  }
  identity slm {
    base lm-packet-type;
    description
      "SLM SOAM PDU generated and received SLR responses tracked.";
  }
  identity ccm {
    base lm-packet-type;
    description
      "CCM SOAM PDU generated and received CCM PDUs tracked.";
  }

  identity dm-packet-type {
    base pm-packet-type;
    description
      "Base identity for the set of Delay Measurement 'types'.";
  }
  identity dmm {
    base dm-packet-type;
    description
      "DMM SOAM PDU generated, DMR responses received (one-way or
       two-way measurements).";
  }
  identity dm1-transmitted {
    base dm-packet-type;
    description
      "1DM SOAM PDU generated (one-way measurements are made by the
       receiver).";
  }
  identity dm1-received {
    base dm-packet-type;
    description
      "1DM SOAM PDU received and tracked (one-way measurements).";
  }

  identity data-tlv-pattern {
    description
      "Base identity for the data patterns that can be used in a
       data TLV";
  }
  identity zeroes {
    base data-tlv-pattern;
    description
      "Indicates the Data TLV contains all zeros.";
  }
  identity ones {
    base data-tlv-pattern;
    description
      "Indicates the Data TLV contains all ones.";
  }

  grouping loss-measurement-configuration-group {
    description
      "This grouping includes configuration objects for the Frame
       Loss Measurement function defined in [Y.1731] and [MEF SOAM PM
       IA].";
    reference 
      "MEF-SOAM-PM-MIB.mefSoamLmCfgTable, [Y.1731] and [MEF SOAM PM
       IA]";

    leaf availability-number-consecutive-flr-measurements {
      if-feature availability;
      type uint32 {
        range "1..1000000";
      }
      default 10;

      description 
        "This object specifies a configurable number of consecutive
         loss measurement PDUs to be used in evaluating the
         availability/unavailability status of each availability
         indicator per MEF 10.2.1.  Loss Measurement PDUs (LMMs, CCMs
         or SLMs) are sent regularly with a period defined by
         message-period.  Therefore, this object, when multiplied by
         message-period, is equivalent to the Availability parameter
         of 'delta_t' as specified by MEF 10.2.1.
                 
         If the measurement-type is lmm or ccm, this object defines
         the number of LMM or CCM PDUs transmitted during each
         'delta_t' period. The Availability flr for a given 'delta_t'
         can be calculated based on the counters in the last LMM/R or
         CCM during this 'delta_t' and the last LMM/R or CCM in the
         previous 'delta_t'.
                 
         If the measurement-type is slm, this object defines the
         number of SLM PDUs transmitted during each 'delta_t' period.
         The Availability flr for a given 'delta_t' is calculated
         based on the number of those SLM PDUs that are lost.
                
         If the measurement-type is lmm or ccm, the number range of 1
         through 10 must be supported. The number range of 10 through
         1000000 may be supported, but is not mandatory.
                
         If the measurement-type is slm, the number range of 10
         through 100 must be supported. The number range of 100
         through 1000000 may be supported, but is not mandatory.";
      reference
        "MEF-SOAM-PM-MIB.
         mefSoamLmCfgAvailabilityNumConsecutiveMeasPdus";
    }

    leaf availability-number-consecutive-intervals {
      if-feature availability;
      type uint32 {
        range "1..1000";
      }
      default 10;

      description 
        "This object specifies a configurable number of consecutive
         availability indicators to be used to determine a change in
         the availability status as indicated by MEF 10.2.1. This
         parameter is equivalent to the Availability parameter of 'n'
         as specified by MEF 10.2.1.
                 
         The number range of 1 through 10 must be supported. The
         number range of 1 through 1000 may be supported, but is not
         mandatory.";
      reference
        "MEF-SOAM-PM-MIB.
         mefSoamLmCfgAvailabilityNumConsecutiveIntervals";
    }

    leaf availability-number-consecutive-high-flr {
      if-feature availability;
      type uint32 {
        range "1..1000";
      }
      default 5;

      description 
        "This object specifies a configurable number of consecutive
         availability indicators to be used for assessing CHLI. This
         parameter is equivalent to the Resilency parameter of 'p' as
         specified by MEF 10.2.1.
                 
         Availability-consecutive-high-flr must be strictly less than
         availability-number-consecutive-intervals. If not, the count
         of high loss intervals over time, and the count of
         consecutive high loss levels, is disabled.
                 
         The number range of 1 through 10 must be supported. The
         number range of 1 through 1000 may be supported, but is not
         mandatory.";
      reference
        "MEF-SOAM-PM-MIB.
         mefSoamLmCfgAvailabilityNumConsecutiveHighFlr";
    }

    container loss-counters {
      description
        "Configuration for enabling LM-specific counters";
      list counter {
        key type;
        description
          "List of LM-specific counter types. A counter type will be
           measured/reported if and only if it is present in this
           list.";

        leaf type {
          type identityref {
            base loss-counter-type;
          }
          description
            "The type of loss counter";
        }
      }
    }
  }

  grouping delay-measurement-configuration-group {
    description
      "This grouping includes configuration objects for the Delay
       Measurement function defined in [Y.1731] and
       [MEF SOAM PM IA].";
    reference 
      "MEF-SOAM-PM-MIB.mefSoamDmCfgTable, [Y.1731], and
       [MEF SOAM PM IA].";

    leaf source-mac-address {
      type yang:mac-address;

      description 
        "The Source MAC Address Field of the received SOAM DM session
         PDUs.
                     
         If measurement-type is dm1-received this object indicates
         the source address of the dm1-transmitted DM session.
                     
         This object is only valid for measurement-type set to
         dm1-received. It is ignored for measurement-type set to dmm
         or dm1-transmitted.";
    }

    leaf ifdv-selection-offset {
      type yang:gauge32 {
        range "1..100";
      }
      default 1;

      description 
        "This object specifies the selection offset for Inter-Frame
         Delay Variation measurements.  If this value is set to n,
         then the IFDV is calculated by taking the difference in
         frame delay between frame F and frame (F+n).";
      reference
        "MEF-SOAM-PM-MIB.
         mefSoamDmCfgInterFrameDelayVariationSelectionOffset";
    }
  }

  grouping configuration-group {
    description
      "This grouping includes configuration objects for PM
       sessions.";

    leaf measurement-type {
      type identityref {
        base pm-packet-type;
      }

      description
        "This object specifies what type of Loss Measurement will be
         performed.
         The exact PDUs to use are specified by this object in
         combination with version";
    }

    leaf version {
      type enumeration {
        enum Y.1731-2008 {
          description
            "Indicates the PDU formats defined in Y.1731-2008";
        }
        enum Y.1731-2011 {
          description
            "Indicates the PDU formats defined in Y.1731-2011.";
        }
      }
      default Y.1731-2008;

      description 
        "This object indicates the version of the PDUs used.

         The exact PDUs to use are specified by this object in
         combination with measurement-type.";
    }

    leaf message-period {
      type performance-monitoring-interval-type;
      units ms;

      description
        "This object specifies the interval between OAM packet
         transmission. For Loss Measurement monitoring applications
         the default value is 1 sec. For Delay Measurement monitoring
         applications, the default value is 100ms.
                 
         This object is not applicable if measurement-type is set to
         'ccm' and is ignored for that Loss Measurement Type.";
    }

    leaf priority {
      type cfm:priority-type;
      mandatory true;

      description 
        "This object specifies the priority of frames with
         Performance Monitoring OAM message information.";
    }

    leaf frame-size {
      type uint32 {
        range "64 .. 9600";
      }
      units bytes;
      default 64;

      description 
        "This object specifies the frame size between 64 bytes
         and the maximum transmission unit of the EVC.
                 
         The range of frame sizes from 64 through 2000 octets need to
         be supported, and the range of frame sizes from 2001 through
         9600 octets is suggested be supported.
                 
         The adjustment to the frame size of the standard frame size
         is accomplished by the addition of a Data or Test TLV. A
         Data or Test TLV is only added to the frame if the frame
         size is greater than 64 bytes.";
    }

    leaf data-pattern {
      type identityref {
        base data-tlv-pattern;
      }
      default zeroes;

      description 
        "This object specifies the data pattern included in a Data
         TLV when the size of the frame is determined by the
         frame-size object and test-tlv-included is 'false'.
                 
         If the frame size object does not define the frame size or
         test-tlv-included is 'true' the value of this object is
         ignored.";
    }

    leaf test-tlv-included {
      type boolean;
      default false;

      description 
        "This object indicates whether a Test TLV or Data TLV is
         included when the size of the frame is determined by the
         frame-size object.
                 
         A value of 'true' indicates that the Test TLV is to be
         included. A value of 'false' indicates that the Data TLV is
         to be included.
                 
         If the frame-size object does not define the frame size the
         value of this object is ignored.";
    }

    leaf test-tlv-pattern {
      type test-pattern-type;
      default null-signal-without-crc-32;

      description 
        "This object specifies the type of test pattern to be sent in
         the frame Test TLV when the size of the PDU is determined by
         the frame-size object and test-tlv-included is 'true'. If
         the frame size object does not define the frame size or
         test-tlv-included is 'false' the value of this object is
         ignored.";
    }

    leaf measurement-interval {
      type uint32 {
        range "1..525600";
      }
      units minutes;
      default 15;

      description 
        "This object specifies the Measurement Interval in minutes.
                 
         A Measurement Interval of 15 minutes needs to be supported,
         other intervals may be supported.";
    }

    leaf number-intervals-stored {
      type uint32 {
        range "2..1000";
      }
      default 32;
      description 
        "This object specifies the number of completed measurement
         intervals to store in the history statistic table.
                 
         At least 32 completed measurement intervals are to be
         stored. 96 measurement intervals are recommended to be
         stored.";
    }

    leaf align-measurement-intervals {
      type boolean;
      default true;

      description 
        "This object specifies whether the Measurement Intervals for
         the session should be aligned with real time.
                 
         The value 'true' indicates that each Measurement Interval
         starts at a time which is aligned to NE time source (with an
         offset determined by align-measurement-offset), if the
         repetition time (or the Measurement Interval, if the
         repetition time is 0) is compatible. If it is not
         compatible, the behaviour is the same as if the object is
         set to 'false'.

         The definition of 'compatible' is device-dependent, but at
         the very least it includes all values that are a factor of
         an hour (i.e. 1, 2, 3, 4, 5, 6, 10, 12, 15, 20, 30 or 60
         minutes). For instance, a Measurement Interval/Repetition
         Time of 15 minutes and an offset of zero minutes would
         stop/start the Measurement Interval at 0, 15, 30, and 45
         minutes of each hour.

         Some devices may also consider values that are a factor
         of 24 hours to be 'compatible', which results in the
         Measurement Intervals being aligned to the time of 00:00
         each day. For instance, a Measurement Interval/Repetition
         Time of 8 hours and an offset of 5 minutes would stop/start
         the Measurement Interval at 00:05, 08:05 and 16:05.

         The value 'false' indicates that the first Measurement
         Interval starts at an arbitrary time and each subsequent
         Measurement Interval starts at a time which is determined by
         repetition-time.";
    }

    leaf align-measurement-offset {
      type uint32 {
        range "0..525600";
      }
      units minutes;
      default 0;

      description 
        "This object specifies the offset in minutes from the time of
         day value if align-measurement-intervals is 'true' and the
         Measurement Interval/Repetition Time is compatible. If not,
         the value of this object is ignored.
                 
         See description of align-measurement-intervals for full
         details.";
    }

    leaf repetition-period {
      type uint32 {
        range "0..31536000";
      }
      units seconds;
      default 0;

      description 
        "This object specifies a configurable repetition time between
         Measurement Intervals in a Measurement session in seconds.
                 
         If the value is less than or equal to one Measurement
         Interval there is no time gap between the end of one
         Measurement Interval and the start of a new Measurement
         Interval. This is the normal usage case.
                 
         If the value is greater than one Measurement Interval there
         is time gap between the end of one Measurement Interval and
         the start of the next Measurement Interval.";
      reference
        "[MEF SOAM PM IA] R18, D3, R19, R20";
    }

    container metrics {
      description
        "Configuration related to specific metric types";
      list metric {
        key metric-type;
        description
          "Configuration for a specific metric type. Metrics will be
           measured/reported if and only if they are present in this
           list.";

        leaf metric-type {
          type identityref {
            base metric-type;
          }
          description
            "The specific metric type that this list entry defines
             the configuration for";
        }

        leaf bin-count {
          type uint32 {
            range "0..100";
          }
          default 1;

          description 
            "This object specifies the number of measurement bins per
             Measurement Interval for this metric. A value of zero
             indicates that no bin statistics should be gathered.
                     
             At least 2 bins are to be supported; at least 10 bins
             are recommended to be supported.";
        }

        list bin {
          key "index";
          description
            "Configuration for a specific bin";

          leaf index {
            type uint32;
            description
              "Index of the bin. The first bin has index 1.";
          }

          leaf lower-bound {
            type uint32;

            description 
              "This object specifies the lower boundary for a
               measurement bin. The upper boundary is defined by the
               next bin value or infinite for the last bin defined.
               The measurement boundary for each measurement bin is
               to be larger than the measurement boundary of the
               preceding measurement bin.

               For delay metrics:
               - The units are milliseconds.
               - By default, each bin boundary is set to 5ms more
                 than the previous bin boundary.

               For loss metrics:
               - For Synthetic Loss, the units are percentage points.
               - For Data Loss, the units are tenths of a percent
               - By default, each bin boundary is set to 1% more
                 than the previous bin boundary.

               The values in a bin boundary object represents the
               range used to segregate data into the appropriate
               statistical data bin. 

               The first bin boundary (index set to 1) always
               contains the value of 0. Attempting to write a
               non-zero value to this bin will result in an error.";
          }
        }
      }
    }

    choice pm-type {
      description
        "Configuration only valid for a specific PM type (LM/DM)";
      case lm {
        when "'derived-from(../measurement-type, lm-packet-type)'" {
          description
            "Configuration only valid for loss measurement";
        }

        uses loss-measurement-configuration-group;
      }
      case dm {
        when "'derived-from(../measurement-type, dm-packet-type)'" {
          description
            "Configuration only valid for delay measurement";
        }

        uses delay-measurement-configuration-group;
      }
    }
  }

  grouping common-stats-group {
    description
      "This grouping includes objects common to current and history
       statistics.";

    leaf id {
      type uint32;

      description 
        "The index for the Measurement Interval
         - In current stats, this is the index of the currently
           running Measurement Interval. This value will become the
           value for id of the history-stats list once the
           Measurement Interval is completed.
         - In history stats, this is the index of the current
           Measurement Interval in the list.";
    }

    leaf start-time {
      type yang:date-and-time;
      mandatory true;

      description
        "The time that this Measurement Interval started.";
    }

    leaf elapsed-time {
      type uint32 {
        range "0..2147483647";
      }
      mandatory true;

      description 
        "The time that the current Measurement Interval has been
         running (in current stats) or ran for (in history stats).
         Units are multiples of 0.01 seconds.";
    }

    leaf suspect-status {
      type suspect-status-type;

      description 
        "Whether the Measurement Interval has been marked as suspect.
                 
         The object is set to false at the start of a measurement
         interval. It is set to true when there is a discontinuity in
         the performance measurements during the Measurement
         Interval.
         Conditions for a discontinuity include, but are not limited
         to the following:
                 
          1 - The local time-of-day clock is adjusted by at least 10
              seconds
          2 - The conducting of a performance measurement is halted
              before the current Measurement Interval is completed
          3 - A local test, failure, or reconfiguration that disrupts
              service";
    }

    leaf soam-pdus-sent {
      type yang:gauge32;
      description 
        "This object contains the count of the number of SOAM PDUs
         sent during this Measurement Interval.
                 
         This object is undefined if measurement-type is
         dm1-received.";
    }

    leaf soam-pdus-received {
      type yang:gauge32;

      description 
        "This object contains the count of the number of SOAM PDUs
         PDUs received in this Measurement Interval.
                 
         This object is undefined if measurement-type is
         dm1-transmitted.";
    }
  }

  grouping metric-stats-group {
    description
      "Statistics for a particular metric for a particular
       Measurement Interval";
    leaf minimum {
      type uint32;
      description
        "The minimum sample value for this metric during the
         Measurement Interval.";
    }
    leaf maximum {
      type uint32;
      description
        "The maximum sample value for this metric during the
         Measurement Interval.";
    }
    leaf average {
      type uint32;
      description
        "The average (mean) sample value for this metric during the
         Measurement Interval.";
    }

    container loss-counters {
      description
        "List of LM-specific counter types. This list is only
         populated for loss measurement sessions.";
      list counter {
        key type;
        description
          "A specific LM counter value";

        leaf type {
          type identityref {
            base loss-counter-type;
          }
          description
            "The type of loss counter";
        }

        leaf value {
          type uint32;
          description
            "The value of the loss counter";
        }
      }
    }

    container bin-stats {
      description
        "Bin-based statistics";
      list bin {
        key number;

        description
          "Statistics for a specific bin";

        leaf number {
          type uint32;

          description 
            "This object specifies the bin number. The first bin has
             bin number 1.";
        }

        leaf lower-bound {
          type uint32;

          description 
            "The lower boundary for this measurement bin. The upper
             boundary is defined by the next bin value or infinite
             for the last bin defined.";
        }

        leaf counter {
          type uint32;

          description 
            "This object contains the count of the number of
             completed measurements initiated in this Measurement
             Interval whose value falls within the range specified
             for this bin (that is, greater than or equal to the
             lower-bound for the bin, and (unless the bin is the last
             bin) less than the lower-bound for the following bin.";
        }
      }
    }
  }

  grouping common-metric-stats-group {
    description
      "This grouping includes per-metric statistics objects common to
       current and history statistics.";

    container metrics {
      description
        "Per-metric statistics";

      list metric {
        key metric-type;
        description
          "Statistics for a specific metric for a specific
           Measurement Interval";

        leaf metric-type {
          type identityref {
            base metric-type;
          }
          description
            "The specific metric type that this list entry contains
             statistics for";
        }

        uses metric-stats-group;
      }
    }
  }

  
  //
  // Augments into CFM related to MEF SOAM PM
  //

  augment "/cfm:maintenance-domain/cfm:maintenance-association" +
          "/cfm:maintenance-association-end-point" {
    description
      "This set of data definitions extends the MEG End Point (as
       described in Y.1731) or Maintenance End Point (as described in
       802.1q) defined in the MEF CFM module (MEF-CFM), specifically
       with regards to the role of the MEP in PM tests.";

    leaf loss-single-ended-responder {
      type boolean;
      default true;

      description 
        "This object specifies whether the Loss Measurement (LMM)
         single-ended Responder is enabled.
                 
         The value 'true' indicates the single-ended Loss Measurement
         Responder is enabled and if a LMM message is received a LMR
         will be sent in re-ply.
                 
         The value 'false' indicates the single-ended Loss
         Measurement Responder is disabled. If a LMM message is
         received no response will be sent and the message will be
         discarded.
                 
         This object needs to be persistent upon reboot or restart of
         a device.
                 
         A MEP can be both a single-ended Responder and Controller
         simultaneously.";
      reference
        "MEF-SOAM-PM-MIB.mefSoamPmMepLmSingleEndedResponder";
    }

    leaf synthetic-loss-single-ended-responder {
      type boolean;
      default true;

      description 
        "This object specifies whether the Synthetic Loss Measurement
         (SLM) single-ended Responder is enabled.
                 
         The value 'true' indicates the single-ended SLM Responder is
         enabled and if a SLM message is received a SLR will be sent
         in reply.
                 
         The value 'false' indicates the single-ended SLM Responder
         is disabled.  If a SLM message is received no response
         will be sent and the message will be discarded.
                 
         This object needs to be persistent upon reboot or restart of
         a device.
                 
         A MEP can be both a single-ended Responder and Controller
         simultaneously.";
      reference
        "MEF-SOAM-PM-MIB.mefSoamPmMepSlmSingleEndedResponsder";
    }

    leaf delay-single-ended-responder {
      type boolean;
      default true;

      description 
        "This object specifies whether the Delay Measurement (DMM)
         single ended Responder is enabled.
                 
         The value 'true' indicates the single-ended Delay
         Measurement Responder is enabled and if a DMM message is
         received a DMR will be sent in reply.
                 
         The value 'false' indicates the single-ended Delay
         Measurement Responder is disabled. If a DMM message is
         received no response will be sent and the message will be
         discarded.
                 
         This object needs to be persistent upon reboot or restart of
         a device.
                 
         A MEP can be both a single-ended Responder and Controller
         simultaneously.";
      reference
        "MEF-SOAM-PM-MIB.mefSoamPmMepDmSingleEndedResponder";
    }
  }

  grouping session-common-group {
    description
      "Operational state common to proactive and on-demand sessions";

    leaf session-id {
      type uint32;
      config false;

      description 
        "This object uniquely identifies a scheduled PM session. It
         is automatically generated by the server on creation of a
         new session.";
    }

    leaf session-status {
      type session-status-type;
      config false;

      description 
        "This object indicates the current status of the PM session.
         A value of 'active' indicates the current PM session is
         active, i.e. the current time lies between the start time
         and the stop time, and enabled is true. A value of
         'not-active' indicates the current PM session is not active,
         i.e. it has not started yet, has stopped upon reaching the
         stop time, or is disabled.";
    }

    container measured-stats {
      config false;
      description
        "Measured statistics - the values obtained in the most
         recent sample";

      choice pm-type {
        description
          "Statistics only valid for a specific PM type (LM/DM)";
        case lm {
          when "'derived-from(../../measurement-type," +
               "lm-packet-type)'" {
            description
              "Statistics only valid for loss measurement";
          }

          leaf availability-forward-status {
            if-feature availability;
            type availability-type;

            description 
              "This object indicates the availability status (the
               outcome of the last availability indicator) in the
               forward direction based upon the last received SOAM
               PDU.";
          }

          leaf availability-backward-status {
            if-feature availability;
            type availability-type;

            description 
              "This object indicates the availability status (the
               outcome of the last availability indicator) in the
               backward direction based upon the last received SOAM
               PDU.";
          }

          leaf forward-last-transition-time {
            if-feature availability;
            type yang:date-and-time;
            description 
              "This object indicates the time of the last transition
               between available and unavailable in the forward
               direction.
                           
               If there have been no transitions since the Loss
               Measurement Session was started, this is set to 0.";
          }

          leaf backward-last-transition-time {
            if-feature availability;
            type yang:date-and-time;
            description 
              "This object indicates the time of the last transition
               between available and unavailable in the backward
               direction.
                           
               If there have been no transitions since the Loss
               Measurement Session was started, this is set to 0.";
          }
        }
      }

      container metrics {
        description
          "Per-metric measured statistics";
        list metric {
          key metric-type;
          description
            "Measured statistics for a specific metric";

          leaf metric-type {
            type identityref {
              base metric-type;
            }
            description
              "The specific metric type that this list entry contains
               measured statistics for";
          }

          leaf value {
            type uint32;
            description
              "The latest sample value for this metric.";
          }
        }
      }
    }

    container current-stats {
      config false;
      description 
        "This container contains the results for the current
         Measurement Interval in a SOAM PM session gathered during
         the interval indicated by measurement-interval.";

      uses common-stats-group;
      uses common-metric-stats-group;
    }

    list history-stats {
      key id;
      config false;
      description 
        "This list contains the results for history Measurement
         Intervals in a SOAM Loss Measurement session.";

      uses common-stats-group;
      uses common-metric-stats-group;
    }
  }

  augment "/cfm:maintenance-domain/cfm:maintenance-association" +
          "/cfm:maintenance-association-end-point" {
    description
      "This set of data definitions extends the MEG End Point (as
       described Y.1731) or Maintenance End Point (as described in
       802.1q) defined in the MEF CFM module (MEF-CFM), specifically
       with regards to Performance Monitoring sessions.";

    container on-demand-sessions {
      description
        "Contains a list of on-demand session information. New
         sessions must be created using the
         'create-session-on-demand' RPC.";

      list on-demand-session {
        key session-id;
        config false;
        description
          "A list of on-demand PM Sessions where each instance is
           uniquely identified by an integer session ID.";

        leaf remote-mep {
          type remote-mep;
          description
            "The remote MEP to which this PM session runs, specified
             by either MEP ID or MAC address.";
        }

        uses configuration-group;
        uses on-demand-timing-group;
        uses session-common-group;
      }
    }

    container proactive-sessions {
      description
        "Contains a list of proactive session information.";
      list proactive-session {
        key "remote-mep name";
        description
          "A list of proactive PM Sessions. New sessions can be
           configured by creating a new entry in this list.";

        leaf remote-mep {
          type remote-mep;
          description
            "The remote MEP to which this PM session runs, specified
             by either MEP ID or MAC address.";
        }

        leaf name {
          type string;
          description
            "A name to uniquely identify this PM session.";
        }

        uses configuration-group;
        uses session-common-group;
      }
    }
  }

  //
  // RPCs related to MEF SOAM PM
  //

  rpc create-session-on-demand {
    description 
      "Schedule a one-way or two-way on-demand performance monitoring
       session on a specific MEP.

       A list entry associated with the newly created session will be
       created in the on-demand-sessions container and the assigned
       session identifier will be returned in the output parameter.";

    input {
      uses cfm:maintenance-association-end-point-reference-group {
        description
          "The MEP on which the session will be started";
      }
      leaf remote-mep {
        type remote-mep;
        description
          "The remote MEP to which this PM session runs, specified
           by either MEP ID or MAC address.";
      }
      uses configuration-group;
      uses on-demand-timing-group;
    }

    output {
      leaf session-id {
        type uint32;
        mandatory true;

        description
          "The session identifier of the newly created PM session.";
      }
    }
  }

  rpc abort-session-on-demand {
    description 
      "Abort a currently running or scheduled on-demand PM session.";

    input {
      uses cfm:maintenance-association-end-point-reference-group {
        description
          "The MEP on which the session should be stopped";
      }

      leaf session-id {
        type uint32;
        mandatory true;

        description
          "The session ID of the PM session to be aborted.";
      }
    }
  }

  rpc clear-history-stats-on-demand {
    description 
      "Clear the historical statistics (history-stats) for a
       specific on-demand PM session. All instance data is deleted.";

    input {
      uses cfm:maintenance-association-end-point-reference-group {
        description
          "The MEP on which the history stats should be cleared";
      }

      leaf session-id {
        type uint32;
        mandatory true;

        description
          "The session ID of the PM session of which the historical
           stats should be cleared. This was returned from the
           create-session-on-demand RPC.";
      }
    }
  }

  rpc clear-history-stats-proactive {
    description 
      "Clear the historical statistics (history-stats) for a
       specific proactive PM session. All instance data is deleted.";

    input {
      uses cfm:maintenance-association-end-point-reference-group {
        description
          "The MEP on which the historical stats should be cleared";
      }

      leaf remote-mep {
        type remote-mep;
        description
          "The remote MEP to which this PM session runs, specified
           by either MEP ID or MAC address.";
      }

      leaf name {
        type string;
        description
          "The name that uniquely identifies this PM session.";
      }
    }
  }

  //
  // Notifications related to MEF SOAM PM
  //

  notification availability-change-alarm {
    if-feature availability;
    description 
      "An availability-change-alarm notification is sent when the
       state of measured-availability-forward-status or
       measured-availability-backward-status associated with a
       specific loss-measurement session changes.";
    reference
      "MEF-SOAM-PM-MIB.mefSoamAvailabilityChangeAlarm";

    uses cfm:maintenance-association-end-point-reference-group {
      description
        "A reference to the specific MEP on which the availability
         change alarm is present";
    }

    leaf session-id {
      type uint32;
      mandatory true;

      description
        "A reference to the loss-measurement session in which the
         availability change alarm occurred.";
    }

    leaf measured-availability-forward-status {
      type availability-type;

      description 
        "The current value of measured-availability-forward-status of
         the referenced loss-measurement session.";
    }

    leaf measured-availability-backward-status {
      type availability-type;

      description 
        "The current value of measured-availability-backward-status
         of the referenced loss-measurement session.";
    }

    leaf measured-forward-last-transition-time {
      type yang:date-and-time;

      description 
        "The current value of measured-forward-last-transition-time
         of the referenced loss-measurement session.";
    }

    leaf measured-backward-last-transition-time {
      type yang:date-and-time;

      description 
        "The current value of measured-backward-last-transition-time
         of the referenced loss-measurement session.";
    }

    leaf forward-available {
      type yang:gauge32;

      description 
        "The current value of forward-available of the referenced
         loss-measurement session.";
    }

    leaf backward-available {
      type yang:gauge32;

      description 
        "The current value of backward-available of the referenced
         loss-measurement session.";
    }

    leaf forward-unavailable {
      type yang:gauge32;

      description 
        "The current value of forward-unavailable of the referenced
         loss-measurement session.";
    }

    leaf backward-unavailable {
      type yang:gauge32;

      description 
        "The current value of backward-unavailable of the referenced
         loss-measurement session.";
    }
  }

  notification session-start-stop-alarm {
    description 
      "A session-start-stop-alarm notification is sent when the state
       of session-status changes for a specific PM session.";

    uses cfm:maintenance-association-end-point-reference-group {
      description
        "A reference to the specific MEP on which the session state
         change alarm occurred.";
    }

    leaf session-id {
      type uint32;
      mandatory true;
          
      description
        "A reference to the PM session in which the session state
         change alarm occurred.";
    }
        
    leaf session-status {
      type session-status-type;

      description 
        "The current value of session-status of the referenced PM
         session.";
    }
  }
}
