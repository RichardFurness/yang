// Contents of "cisco-xr-soam-pm"
module cisco-xr-soam-pm {
  namespace "urn:cisco:params:xml:ns:yang:cisco-xr-soam-pm";
  prefix "cisco-xr-soam-pm";
  
  import cisco-cfm {
    prefix cfm;
    revision-date 2015-09-29;
  }
  import cisco-soam-pm {
    prefix soam-pm;
    revision-date 2015-09-29;
  }
  
  organization
    "Cisco Systems, Inc.
     Customer Service

     Postal: 170 W Tasman Drive
     San Jose, CA 95134

     Tel: +1 1800 553-NETS
     
     E-mail: cs-yang@cisco.com";

  contact
    "Richard Furness - rfurness@cisco.com";
  
  description 
    "This YANG module extends the Cisco Service OAM PM module with
     IOS-XR-specific augmentations and deviations";
  
  revision 2015-09-29 {
    description "Initial revision";
  }

  /*
   * Burst config typedefs
   */
  typedef burst-interval-units {
    type enumeration {
      enum Hours {
        description
          "Send bursts within a probe with an interval unit of
           hours.";
      }
      enum Minutes {
        description
          "Send bursts within a probe with an interval unit of
           minutes.";
      }
      enum Seconds {
        description
          "Send bursts within a probe with an interval unit of
           seconds.";
      }
      enum Once {
        description
          "Send one burst per probe.";
      }
    }

    description
      "Enumeration of units of time to apply to the burst interval
       value.";
  }

  /*
   * Schedule config typedefs
   */
  typedef probe-duration-units {
    type enumeration {
      enum seconds {
        description
          "Schedule probes to run with a duration unit of seconds";
      }
      enum minutes {
        description
          "Schedule probes to run with a duration unit of minutes";
      }
      enum hours {
        description
          "Schedule probes to run with a duration unit of hours";
      }
      enum day {
        description
          "Schedule probes to run for a duration of 1 day";
      }
      enum week {
        description
          "Schedule probes to run for a duration of 1 week";
      }
    }
    description "Probe duration units enum";
  }

  typedef probe-interval-units {
    type enumeration {
      enum minutes {
        description
          "Schedule probes to run with an interval unit of minutes";
      }
      enum hours {
        description
          "Schedule probes to run with an interval unit of hours";
      }
      enum day {
        description
          "Schedule probes to run every day";
      }
      enum week {
        description
          "Schedule probes to run every week";
      }
    }
    description "Probe interval units enum";
  }

  typedef probe-interval-day {
    type enumeration {
      enum monday {
        description "Schedule every Monday";
      }
      enum tuesday {
        description "Schedule every Tuesday";
      }
      enum wednesday {
        description "Schedule every Wednesday";
      }
      enum thursday {
        description "Schedule every Thursday";
      }
      enum friday {
        description "Schedule every Friday";
      }
      enum saturday {
        description "Schedule every Saturday";
      }
      enum sunday {
        description "Schedule every Sunday";
      }
    }
    description "Probe interval day enum";
  }

  /*
   * Arbitrary hex values for Data TLV
   */
  identity hex-4-bytes {
    base soam-pm:data-tlv-pattern;
    description
      "Indicates the Data TLV contains a 4-byte pattern repeated as
       necessary to the end of the TLV.";
  }
  
  /*
   * Per-operation configuration to be augmented
   */
  grouping per-operation-config-group {
    /*
     * Burst configuration
     */
    leaf burst-interval {
      type uint32 {
        range "1 .. 3600";
      }
      description
        "Interval between bursts. This must be specified if, and only
         if, the burst-enabled is True and burst-interval-unit is not
         'once'.";
    }
    leaf burst-interval-unit {
      type burst-interval-units;
      description
        "Time unit associated with the burst-interval.  This must be
         specified if, and only if, burst-enabled is True.";
    }
    leaf burst-packet-count {
      type uint32 {
        range "2 .. 1200";
      }
      description
        "The number of packets in each burst.  This must be specified
         if, and only if, burst-enabled is True.";
    }
    leaf burst-enabled {
      type boolean;
      description
        "Whether or not packets should be sent in bursts. If True,
         both burst-packet-count and burst-interval-unit must be
         specified.";
    }

    /*
     * Arbitrary hex values for Data TLV
     */
    leaf data-pattern-hex {
      type uint32;
      must "../data-pattern = 'hex-4-bytes'";
      description
        "If data-pattern is 'hex-4-bytes', this leaf contains a
         4-byte arbitrary data pattern, represented as the 32-bit
         unsigned integer that would take this form when in
         big-endian format. The data TLV is filled with as many
         repetitions of this pattern as are required to pad the
         packet to the specified size.";
    }

    /*
     * Schedule configuration
     */
    leaf probe-interval {
      type uint32 {
        range "1..90";
      }
      description
        "Interval between probes.  This must be specified if, and
         only if, probe-interval-unit is not 'Week' or 'Day'.";
    }
    leaf probe-interval-day {
      type probe-interval-day;
      description
        "Day of week on which to schedule probes. This must be
         specified if, and only if, probe-interval-unit is 'Week'.";
    }
    leaf probe-interval-unit {
      type probe-interval-units;
      description
        "Time unit associated with the probe-interval. The value must
         not be 'Once'.  If 'Week' or 'Day' is specified, probes are
         scheduled weekly or daily respectively.";
    }
    leaf start-time-hour {
      type uint32 {
        range "0..23";
      }
      description
        "Time after midnight (in UTC) to send the first packet each
         day.";
    }
    leaf start-time-minute {
      type uint32 {
        range "0..59";
      }
      description
        "Time after midnight (in UTC) to send the first packet each
         day. This must be specified if, and only if, start-time-hour
         is specified.";
    }
    leaf start-time-second {
      type uint32 {
        range "0..59";
      }
      description
        "Time after midnight (in UTC) to send the first packet each
         day. This must only be specified if start-time-hour is
         specified, and must not be specified if probe-interval-unit
         is 'Week' or 'Day'.";
    }
    leaf probe-duration {
      type uint32;
      description
        "Duration of each probe.  This must be specified if, and only
         if, probe-duration-unit is specified.";
    }
    leaf probe-duration-unit {
      type probe-duration-units;
      description
        "Time unit associated with the probe-duration.";
    }
  }

  /*
   * Per-metric configuration to be augmented
   */
  grouping per-metric-config-group {
    leaf probes-per-bucket {
      type uint32;
      default 1;
      description
        "This value acts as a multiplier to increase the Measurement
         Interval duration to a multiple of the duration defined by
         'repetition-period' in the base model. This has no impact on
         the scheduling of the SOAM PDUs, but simply causes PM
         statistics to be aggregated over a longer period of time.";
    }
    leaf bin-width {
      type uint32 {
        range "1..10000";
      }

      description 
        "This object specifies the width of each bin for this
         particular metric.
                 
         For Delay and IFDV, the units are milliseconds.
         For Synthetic Loss, the units are percentage points (and the
         maximum value is 100).
         For Data Loss, the units are tenths of a percent (and the
         maximum value is 1000)";
    }
    leaf number-intervals-stored {
      type uint32 {
        range "2..1000";
      }
      default 32;
      description 
        "This object specifies the number of completed measurement
         intervals to store in the history statistic table.
                 
         At least 32 completed measurement intervals are to be
         stored. 96 measurement intervals are recommended to be
         stored.";
    }
  }

  /*
   * Augment the create-session-on-demand RPC to add Cisco-specific
   * options
   */
  augment "/soam-pm:create-session-on-demand/soam-pm:input" {
    uses per-operation-config-group;
  }
  augment "/soam-pm:create-session-on-demand/soam-pm:input"+
          "/soam-pm:metrics/soam-pm:metric" {
    uses per-metric-config-group;
  }

  /*
   * New top-level list for PM Profile configuration
   */
  container pm-profiles {
    description
      "Profiles allow PM configuration to be shared between multiple
       PM sessions";
    list pm-profile {
      key name;
      description
        "Contains profiles for PM session configuration";

      leaf name {
        type string;
        description
          "The name of the LM profile";
      }

      uses soam-pm:configuration-group {
        augment "metrics/metric" {
          uses per-metric-config-group;
        }
      }
      uses per-operation-config-group;
    }
  }

  /*
   * Augment proactive session table with profile reference and
   * XR-specific config
   */
  augment "/cfm:maintenance-domain/cfm:maintenance-association" +
          "/cfm:maintenance-association-end-point"+
          "/soam-pm:proactive-sessions" +
          "/soam-pm:proactive-session" {
    leaf pm-profile {
      type leafref {
        path "/pm-profiles/pm-profile/name";
      }
      description
        "Reference to a PM configuration profile to use for this
         session.";
    }

    uses per-operation-config-group;
  }
  augment "/cfm:maintenance-domain/cfm:maintenance-association" +
          "/cfm:maintenance-association-end-point"+
          "/soam-pm:proactive-sessions" +
          "/soam-pm:proactive-session"+
          "/soam-pm:metrics/soam-pm:metric" {
    uses per-metric-config-group;
  }
  

  /*
   * New DM measurement type (packet type)
   */
  identity lbm {
    base soam-pm:dm-packet-type;
    description
      "Use loopback PDUs (LBM/LBR).";
  }

  /*
   * Oper: augment on-demand table with XR-specific config
   */
  augment "/cfm:maintenance-domain/cfm:maintenance-association" +
          "/cfm:maintenance-association-end-point"+
          "/soam-pm:on-demand-sessions" +
          "/soam-pm:on-demand-session" {
    uses per-operation-config-group;
  }
  augment "/cfm:maintenance-domain/cfm:maintenance-association" +
          "/cfm:maintenance-association-end-point"+
          "/soam-pm:on-demand-sessions" +
          "/soam-pm:on-demand-session"+
          "/soam-pm:metrics/soam-pm:metric" {
    uses per-metric-config-group;
  }

  /*
   * Oper: support different bucket lengths for each metric 
   */
  grouping per-metric-bucket-list-group {
    container metrics-stats {
      config false;
      description
        "Statistic for all metrics gathered for this session";

      list metric-stats {
        key metric-type;
        description
          "Statistics for a specific metric";

        leaf metric-type {
          type identityref {
            base soam-pm:metric-type;
          }
          description
            "The specific metric type that this list entry contains
             statistics for";
        }

        container buckets {
          description
            "Contains a list of buckets (measurement intervals)";
          list bucket {
            key id;
            description
              "The statistics for an individual bucket (measurement
               interval)";

            uses soam-pm:common-stats-group;
            uses soam-pm:metric-stats-group;
          }
        }
      }
    }
  }
  augment "/cfm:maintenance-domain/cfm:maintenance-association" +
          "/cfm:maintenance-association-end-point"+
          "/soam-pm:proactive-sessions/soam-pm:proactive-session" {
    uses per-metric-bucket-list-group;
  }
  augment "/cfm:maintenance-domain/cfm:maintenance-association" +
          "/cfm:maintenance-association-end-point"+
          "/soam-pm:on-demand-sessions/soam-pm:on-demand-session" {
    uses per-metric-bucket-list-group;
  }

  /*
   * Oper: Unaggregated results
   */
  grouping samples-group {
    container samples {
      description
        "Contains a list of every sample recorded for this metric
         during this measurement inverval";
      list sample {
        description
          "Details of an individual sample";

        leaf sent-at {
          type uint32;
          mandatory true;
          description
            "The time (in milliseconds relative to the start time of
             the measurement interval) that the sample was sent at";
        }

        leaf sent {
          type boolean;
          mandatory true;
          description
            "Whether the sample packet was successfully sent";
        }

        leaf timed-out {
          type boolean;
          mandatory true;
          description
            "Whether the sample packet timed out";
        }

        leaf corrupt {
          type boolean;
          mandatory true;
          description
            "Whether the sample packet was corrupt";
        }

        leaf out-of-order {
          type boolean;
          mandatory true;
          description
            "Whether the sample packet was received out-of-order";
        }

        leaf result {
          type int32;
          description
            "The result (in microseconds or millionths of a percent)
             of the sample, if available";
        }

        container flr {
          description
            "Leaves specified to loss measurement";
          leaf no-data {
            type boolean;
            description
              "Whether a measurement could not be made because no
               data packets were sent in the sample period. Only
               applicable for LMM measurements";
          }
          leaf frames-sent {
            type uint32;
            description
              "For FLR measurements, the number of frames sent, if
               available";
          }

          leaf frames-lost {
            type uint32;
            description
              "For FLR measurements, the number of frames lost, if
               available";
          }
        }
      }
    }
  }

  augment "/cfm:maintenance-domain/cfm:maintenance-association" +
          "/cfm:maintenance-association-end-point"+
          "/soam-pm:proactive-sessions/soam-pm:proactive-session"+
          "/soam-pm:current-stats/soam-pm:metrics/soam-pm:metric" {
    uses samples-group;
  }
  augment "/cfm:maintenance-domain/cfm:maintenance-association" +
          "/cfm:maintenance-association-end-point"+
          "/soam-pm:on-demand-sessions/soam-pm:on-demand-session"+
          "/soam-pm:current-stats/soam-pm:metrics/soam-pm:metric" {
    uses samples-group;
  }
  augment "/cfm:maintenance-domain/cfm:maintenance-association" +
          "/cfm:maintenance-association-end-point"+
          "/soam-pm:proactive-sessions/soam-pm:proactive-session"+
          "/soam-pm:history-stats/soam-pm:metrics/soam-pm:metric" {
    uses samples-group;
  }
  augment "/cfm:maintenance-domain/cfm:maintenance-association" +
          "/cfm:maintenance-association-end-point"+
          "/soam-pm:on-demand-sessions/soam-pm:on-demand-session"+
          "/soam-pm:history-stats/soam-pm:metrics/soam-pm:metric" {
    uses samples-group;
  }

  augment "/cfm:maintenance-domain/cfm:maintenance-association" +
          "/cfm:maintenance-association-end-point"+
          "/soam-pm:proactive-sessions/soam-pm:proactive-session"+
          "/metrics-stats/metric-stats/buckets/bucket" {
    uses samples-group;
  }
  augment "/cfm:maintenance-domain/cfm:maintenance-association" +
          "/cfm:maintenance-association-end-point"+
          "/soam-pm:on-demand-sessions/soam-pm:on-demand-session"+
          "/metrics-stats/metric-stats/buckets/bucket" {
    uses samples-group;
  }

  
  /*
   * Deviations
   */
  deviation "/cfm:maintenance-domain/cfm:maintenance-association" +
            "/cfm:maintenance-association-end-point" +
            "/soam-pm:on-demand-sessions" +
            "/soam-pm:on-demand-session" +
            "/soam-pm:measured-stats" {
    description
      "Measured statistics are not supported in XR";
    deviate not-supported;
  }
  deviation "/cfm:maintenance-domain/cfm:maintenance-association" +
            "/cfm:maintenance-association-end-point" +
            "/soam-pm:proactive-sessions" +
            "/soam-pm:proactive-session" +
            "/soam-pm:measured-stats" {
    description
      "Measured statistics are not supported in XR";
    deviate not-supported;
  }
}
